-- Palo Alto Networks-style trap definitions (the shapes of PAN-TRAPS; for SheepLog's tests, a
-- handful of the several hundred objects and notifications).

PAN-TRAPS DEFINITIONS ::= BEGIN

IMPORTS
	MODULE-IDENTITY, OBJECT-TYPE, NOTIFICATION-TYPE, Integer32, Counter64
		FROM SNMPv2-SMI
	DisplayString
		FROM SNMPv2-TC
	panModules
		FROM PAN-GLOBAL-REG
	panCommonEventObjs, panCommonEventEventsV2
		FROM PAN-COMMON-MIB;

panTrapsModule MODULE-IDENTITY
	LAST-UPDATED "202006011200Z"
	ORGANIZATION "Palo Alto Networks"
	CONTACT-INFO "support@paloaltonetworks.com"
	DESCRIPTION  "Traps generated by PAN-OS for log forwarding to SNMP"
	::= { panModules 5 }

-- Var-binds carried by the traps.

panReceiveTime OBJECT-TYPE
	SYNTAX		OCTET STRING (SIZE(0..64))
	MAX-ACCESS	accessible-for-notify
	STATUS		current
	DESCRIPTION	"Time the log was received at the management plane"
	::= { panCommonEventObjs 2 }

panSerial OBJECT-TYPE
	SYNTAX		OCTET STRING (SIZE(0..64))
	MAX-ACCESS	accessible-for-notify
	STATUS		current
	DESCRIPTION	"Serial number of the device that generated the log"
	::= { panCommonEventObjs 3 }

panEventType OBJECT-TYPE
	SYNTAX		OCTET STRING (SIZE(0..64))
	MAX-ACCESS	accessible-for-notify
	STATUS		current
	DESCRIPTION	"Specifies type of log"
	::= { panCommonEventObjs 4 }

panEventSubType OBJECT-TYPE
	SYNTAX		OCTET STRING (SIZE(0..64))
	MAX-ACCESS	accessible-for-notify
	STATUS		current
	DESCRIPTION	"Subtype of the log"
	::= { panCommonEventObjs 5 }

panHostname OBJECT-TYPE
	SYNTAX		OCTET STRING (SIZE(0..64))
	MAX-ACCESS	accessible-for-notify
	STATUS		current
	DESCRIPTION	"Hostname of the firewall"
	::= { panCommonEventObjs 6 }

panSeverity OBJECT-TYPE
	SYNTAX		INTEGER {
		unused(0),
		informational(1),
		low(2),
		medium(3),
		high(4),
		critical(5)
	}
	MAX-ACCESS	accessible-for-notify
	STATUS		current
	DESCRIPTION	"Severity associated with the event"
	::= { panCommonEventObjs 7 }

panSystemDescription OBJECT-TYPE
	SYNTAX		OCTET STRING (SIZE(0..1024))
	MAX-ACCESS	accessible-for-notify
	STATUS		current
	DESCRIPTION	"Detailed description of the event"
	::= { panCommonEventObjs 8 }

-- Notifications.

panGeneralSystemTrap NOTIFICATION-TYPE
	OBJECTS { panReceiveTime, panSerial, panEventType, panEventSubType, panHostname,
	          panSeverity, panSystemDescription }
	STATUS	current
	DESCRIPTION "General system event"
	::= { panCommonEventEventsV2 500 }

panHAStateChangeTrap NOTIFICATION-TYPE
	OBJECTS { panReceiveTime, panSerial, panHostname, panSeverity, panSystemDescription }
	STATUS	current
	DESCRIPTION "HA state change"
	::= { panCommonEventEventsV2 543 }

panLinkDownTrap NOTIFICATION-TYPE
	OBJECTS { panReceiveTime, panSerial, panHostname, panSeverity, panSystemDescription }
	STATUS	current
	DESCRIPTION "Link down"
	::= { panCommonEventEventsV2 531 }

panGPGatewayConfigReleaseTrap NOTIFICATION-TYPE
	OBJECTS { panReceiveTime, panSerial, panHostname, panSeverity, panSystemDescription }
	STATUS	current
	DESCRIPTION "GlobalProtect gateway released a client configuration"
	::= { panCommonEventEventsV2 1300 }

END
